-- SPDX-License-Identifier: BSD-3-Clause
--
-- Copyright (C) 2016 IETF Trust and the persons identified as authors
-- of the code
--
-- https://www.rfc-editor.org/rfc/rfc8017#appendix-A.1.1

RsaPubKey ::= SEQUENCE {
	n INTEGER ({ x509_rsa_note_n }),
	e INTEGER ({ x509_rsa_note_e })
}
